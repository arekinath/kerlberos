SPNEGO {iso(1) identified-organization(3) dod(6) internet(1) security(5) mechanisms(5) snego(2)}
-- (1.3.6.1.5.5.2)
DEFINITIONS ::=

BEGIN

MechType::= OBJECT IDENTIFIER

id-gssapi OBJECT IDENTIFIER ::= {
    iso(1) member-body(2) us(840) mit(113554) infosys(1) gssapi(2)
}
id-spnego OBJECT IDENTIFIER ::= {
    iso(1) identified-organization(3) dod(6) internet(1) security(5) mechanisms(5) snego(2)
}

id-user-name OBJECT IDENTIFIER ::= { id-gssapi generic(1) user-name(1) }
id-machine-uid-name OBJECT IDENTIFIER ::= { id-gssapi generic(1) machine-uid-name(2) }
id-string-uid-name OBJECT IDENTIFIER ::= { id-gssapi generic(1) string-uid-name(3) }
id-service-name OBJECT IDENTIFIER ::= { id-gssapi generic(1) service-name(4) }
id-krb5-name OBJECT IDENTIFIER ::= { id-gssapi krb5(2) krb5-name(1) }

id-ms-mechs OBJECT IDENTIFIER ::= {
    iso(1) identified-organization(3) dod(6) internet(1) private(4) enterprise(1) microsoft(311)
    security(2) mechanisms(2)
}
id-mech-spnego OBJECT IDENTIFIER ::= { id-spnego }
id-mech-snegoex OBJECT IDENTIFIER ::= { id-ms-mechs snegoex(30) }
id-mech-ntlm OBJECT IDENTIFIER ::= { id-ms-mechs ntlm(10) }
id-mech-krb5 OBJECT IDENTIFIER ::= { id-gssapi krb5(2) }
id-mech-krb5-usertouser OBJECT IDENTIFIER ::= { id-gssapi krb5(2) usertouser(3) }

NegotiationToken ::= CHOICE {
                              negTokenInit  [0]  NegTokenInit,
                              negTokenResp  [1]  NegTokenResp }

MechTypeList ::= SEQUENCE OF MechType

NegHints ::= SEQUENCE {
    hintName    [0] GeneralString  OPTIONAL,
    hintAddress [1] OCTET STRING   OPTIONAL
}

NegTokenInit ::= SEQUENCE {
    mechTypes       [0] MechTypeList  OPTIONAL,
    reqFlags        [1] ContextFlags  OPTIONAL,
    mechToken       [2] OCTET STRING  OPTIONAL,
    negHints        [3] NegHints      OPTIONAL,
    mechListMIC     [5] OCTET STRING  OPTIONAL
}

ContextFlags ::= BIT STRING {
    delegFlag       (0),
    mutualFlag      (1),
    replayFlag      (2),
    sequenceFlag    (3),
    anonFlag        (4),
    confFlag        (5),
    integFlag       (6)
}

NegTokenResp ::= SEQUENCE {
    negState       [0] ENUMERATED {
                            accept-completed    (0),
                            accept-incomplete   (1),
                            reject              (2),
                            request-mic         (3) }          OPTIONAL,
    supportedMech  [1] MechType                                OPTIONAL,
    responseToken  [2] OCTET STRING                            OPTIONAL,
    mechListMIC    [3] OCTET STRING                            OPTIONAL
}

--GSS-API DEFINITIONS ::= 
--BEGIN 
--MechType ::= OBJECT IDENTIFIER 
-- data structure definitions 
-- callers must be able to distinguish among 
-- InitialContextToken, SubsequentContextToken, 
-- PerMsgToken, and SealedMessage data elements 
-- based on the usage in which they occur 
InitialContextToken ::= 
	-- option indication (delegation, etc.) indicated within 
	-- mechanism-specific token 
[APPLICATION 0] IMPLICIT SEQUENCE { 
	thisMech MechType, 
	innerContextToken InnerContextToken 
	--	DEFINED BY thisMech 
	-- contents mechanism-specific 
	-- ASN.1 structure not required
	 } 

-- SubsequentContextToken ::= InnerContextToken

InnerContextToken ::= ANY
-- interpretation based on predecessor InitialContextToken 
-- ASN.1 structure not required 

-- PerMsgToken ::= 
-- as emitted by GSS_GetMIC and processed by GSS_VerifyMIC 
-- ASN.1 structure not required 
--	InnerMsgToken

-- InnerMsgToken ::= ANY

-- SealedMessage ::= 
-- as emitted by GSS_Wrap and processed by GSS_Unwrap 
-- includes internal, mechanism-defined indicator 
-- of whether or not encrypted 
-- ASN.1 structure not required 
--	SealedUserData 
	
-- SealedUserData ::= ANY 

-- END GSS-API DEFINITIONS

END
